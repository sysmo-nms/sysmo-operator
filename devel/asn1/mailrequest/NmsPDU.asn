NmsPDU DEFINITIONS IMPLICIT TAGS ::=
-- Use the DEFINITIONS EXPLICIT TAGS in your definition file.
-- Due to limitation in Tcl/ASN library BER encoding functions, follow these 
-- rules if you plan to use it. For example, the default Tkorder client:
-- * define tags in CHOICE constructs
-- * do not define tags in SEQUENCE constructs
-- * do not use SET constructs

BEGIN
EXPORTS PDU;

IMPORTS 
--    SupercastPDU    FROM ModSupercast
--    EsnmpPDU        FROM ModEsnmp
    TestPDU         FROM ModTest
    TrackerPDU      FROM ModTracker;

PDU ::= CHOICE {
--    modSupercastPDU [0] SupercastPDU,
    modTest         [1] TestPDU,
    modTrackerPDU   [2] TrackerPDU
}

END
